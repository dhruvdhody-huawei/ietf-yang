module ietf-te-wson{

  namespace "urn:ietf:params:xml:ns:yang:ietf-te-wson";

  prefix "te-wson";

  import ietf-te {
    prefix "te";
  }

  import ietf-te-device {
    prefix "te-dev";
  }

  organization
    "IETF CCAMP Working Group";

  contact
    "WG Web:   <http://tools.ietf.org/wg/ccamp/>
     WG List:  <mailto:ccamp@ietf.org>

     WG Chair: Daniele Ceccarelli 
               <mailto:daniele.ceccarelli@ericsson.com>

     WG Chair: Fatai Zhang 
               <mailto:zhangfatai@huawei.com>

     Editor: Young Lee <leeyoung@huawei.com>
     Editor: Dhruv Dhody <dhruv.ietf@gmail.com>
     Editor: Ricard Vilalta <ricard.vilalta@cttc.es>";

 description
    "Latest update to WSON TE YANG data model.";

  revision "2017-06-21" {
    description "Update to WSON TE YANG initial revision.";
    reference "xxxx";
  }

  identity wavelength-assignment {
    description "Wavelength selection base";
  }

  identity unspecified-wavelength-assignment {
    base wavelength-assignment;
    description "No method specified";
  }

  identity first-fit-wavelength-asignment {
    base wavelength-assignment;
    description "All the available wavelengths are numbered, 
    	and this WA method chooses the available wavelength 
    	with the lowest index.";
  }

  identity random-wavelength-asignment {
    base wavelength-assignment;
    description "This WA method chooses an available 
    	wavelength randomly.";
  }

  identity least-loaded-wavelength-asignment {
    base wavelength-assignment;
    description "This WA method selects the wavelength that 
    	has the largest residual capacity on the most loaded 
    	link along the route (in muli-fiber networks).";
  }

  /* TE WSON LSPs groupings */
  grouping lsp-attributes-flags-wson_config {
    description
      "Configuration parameters relating to TE WSON LSP
      attribute flags";

    leaf wavelength-assignment {
      type identityref {
        base wavelength-assignment;
      }
      description "Wavelength Allocation Method";
    }

    leaf selected-frequency {
      type decimal64 {
        fraction-digits 5;
      }
      units THz;
      default 193.1;
      description "Selected Central Frequency";
    }

    leaf channel-spacing {
      type decimal64 {
        fraction-digits 5;
      }
      units GHz;
      description "This is fixed channel spacing for 
      	WSON, e.g, 12.5, 25, 50, 100, ..";
    }

  }

  grouping tunnel-properties-wson {
    description
      "Top level grouping for LSP properties.";
        uses lsp-attributes-flags-wson_config;
  }

  grouping lsp-properties-wson {
    description
      "Top level grouping for LSP properties.";
      uses lsp-attributes-flags-wson_config;
  }
  /* End of TE WSON LSPs groupings */

  /**
   * Interface groupings
   */
  grouping wson-reservable {
    description "Top level grouping for interface properties";
    leaf selected-frequency {
      type decimal64 {
        fraction-digits 5;
      }
      units THz;
      default 193.1;
      description "Selected Central Frequency";
    }

    leaf channel-spacing {
      type decimal64 {
        fraction-digits 5;
      }
      units GHz;
      description "This is fixed channel spacing for WSON,
                e.g, 12.5, 25, 50, 100, ..";
     }
  }

   /* End of interface groupings */

  /**
   * Augmentation to TE generic module
   */
  augment "/te:te/te:tunnels/te:tunnel/te:config" {
    description
      "Augmentations for WSON TE tunnel properties";
    uses tunnel-properties-wson;
  }

  augment "/te:te/te:tunnels/te:tunnel/te:state" {
    description
      "Augmentations for WSON TE tunnel properties";
    uses tunnel-properties-wson;
  }

  augment "/te:te/te:lsps-state/te:lsp" {
    description
      " WSON LSP state properties";
    uses lsp-properties-wson;
  }

  augment "/te:te/te-dev:interfaces/te-dev:interface" {
    description
      "WSON reservable bandwidth configuration properties";
    uses wson-reservable;
  }

}
